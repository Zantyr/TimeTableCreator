(defun avg(lista/num i x y z)
	 (setq num (length lista) x 0.0 y 0.0 z 0.0)
	(foreach i lista (setq x (+ x (nth 0 i)) y (+ y (nth 1 i)) z (+ z (nth 2 i)) ) )
  	(setq x (/ x num) y (/ y num) z (/ z num))
  	(command "_circle" '(x y z) 10)
	)

(defun XD(/ p l i)
	(setq i 3)
	(setq p (getpoint "Gimme da point: "))
	(while (not (null p))
		(command "_circle" p i)
		(setq i (+ i 3))
		(setq l (append l (list p)))
		(setq p (getpoint "Giveth-thou ye nexte pointe: "))
		)
  	(print l)
  	(avg l)
	(eval 'l)
	)
